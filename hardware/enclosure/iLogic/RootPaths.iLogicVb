' ============================================================
' iLogic: Wurzel-Pfade + Sweep für Baumstamm-Basis (v3)
' L-förmige Z-Kurve + elliptisches Profil (breit/flach)
' Zwei Klassen: Hauptwurzeln (breite Rippen) + Nebenwurzeln
' Datei: hardware/enclosure/iLogic/RootPaths.iLogicVb
' ============================================================
' ANLEITUNG:
' 1. Öffne master.ipt in Inventor (Stamm-Zylinder muss existieren)
' 2. iLogic → Regel hinzufügen → Code einfügen
' 3. Parameter anpassen (siehe unten)
' 4. Ausführen → erzeugt Wurzel-Bodies (Join)
' 5. Falls Sweep fehlschlägt: 3D-Splines bleiben erhalten
' 6. Fillets manuell setzen (2min, volle Kontrolle)
' ============================================================

' === PARAMETER (hier anpassen) ===
Dim stammRadius As Double = 10.2      ' cm (Ø204mm / 2) – konsistent mit BarkPaths!
Dim seed As Integer = 99              ' Bewusst ≠ BarkPaths (42)

' Hauptwurzeln (breite Rippen, wie Strebepfeiler)
Dim anzahlHaupt As Integer = 4        ' dicke Hauptwurzeln
Dim hauptLaenge As Double = 7.0       ' cm radiale Ausdehnung
Dim hauptAbsenkung As Double = 1.5    ' cm Tiefe unter Z=0 am Ende
Dim hauptAnstieg As Double = 1.5      ' cm Startpunkt über Z=0 am Stamm
Dim hauptBreite As Double = 3.2       ' cm Breite (tangential) am Stamm
Dim hauptHoehe As Double = 1.3        ' cm Höhe (vertikal) am Stamm → Aspect ~2.5:1
Dim hauptBreiteSpitze As Double = 0.5 ' cm Breite an der Spitze
Dim hauptHoeheSpitze As Double = 0.3  ' cm Höhe an der Spitze

' Nebenwurzeln (dünn, kürzer)
Dim anzahlNeben As Integer = 5        ' dünne Nebenwurzeln
Dim nebenLaenge As Double = 4.5       ' cm radiale Ausdehnung
Dim nebenAbsenkung As Double = 1.0    ' cm Tiefe unter Z=0
Dim nebenAnstieg As Double = 0.6      ' cm Startpunkt über Z=0
Dim nebenBreite As Double = 1.2       ' cm Breite am Stamm → Aspect ~2:1
Dim nebenHoehe As Double = 0.6        ' cm Höhe am Stamm
Dim nebenBreiteSpitze As Double = 0.3 ' cm Breite an der Spitze
Dim nebenHoeheSpitze As Double = 0.2  ' cm Höhe an der Spitze

' Gemeinsame Parameter
Dim punkteProWurzel As Integer = 10   ' Spline-Kontrollpunkte (mehr = glatter)
Dim welligkeit As Double = 0.08       ' cm laterale Variation (minimal)
Dim laengenVariation As Double = 0.35 ' 0-1: Längenunterschied
Dim winkelVariation As Double = 0.7   ' 0-1: Unregelmäßigkeit der Verteilung

' === SETUP ===
Dim oDoc As PartDocument = ThisApplication.ActiveDocument
Dim oDef As PartComponentDefinition = oDoc.ComponentDefinition
Dim oTG As TransientGeometry = ThisApplication.TransientGeometry
Dim rng As New Random(seed)
Dim PI As Double = Math.PI
Dim anzahlGesamt As Integer = anzahlHaupt + anzahlNeben

' === CLEANUP: Alte Root_-Elemente löschen (für Re-Run) ===
Dim featsToDelete As New List(Of SweepFeature)
For Each feat As SweepFeature In oDef.Features.SweepFeatures
    If feat.Name.StartsWith("Root_") Then featsToDelete.Add(feat)
Next
For Each feat As SweepFeature In featsToDelete
    Try : feat.Delete() : Catch : End Try
Next

Dim filletsToDelete As New List(Of FilletFeature)
For Each feat As FilletFeature In oDef.Features.FilletFeatures
    If feat.Name.StartsWith("Root_") Then filletsToDelete.Add(feat)
Next
For Each feat As FilletFeature In filletsToDelete
    Try : feat.Delete() : Catch : End Try
Next

Dim sketches2DToDelete As New List(Of PlanarSketch)
For Each sk As PlanarSketch In oDef.Sketches
    If sk.Name.StartsWith("Root_") Then sketches2DToDelete.Add(sk)
Next
For Each sk As PlanarSketch In sketches2DToDelete
    Try : sk.Delete() : Catch : End Try
Next

Dim sketches3DToDelete As New List(Of Sketch3D)
For Each sk As Sketch3D In oDef.Sketches3D
    If sk.Name.StartsWith("Root_") Then sketches3DToDelete.Add(sk)
Next
For Each sk As Sketch3D In sketches3DToDelete
    Try : sk.Delete() : Catch : End Try
Next

Dim wpToDelete As New List(Of WorkPlane)
For Each wp As WorkPlane In oDef.WorkPlanes
    If wp.Name.StartsWith("Root_") Then wpToDelete.Add(wp)
Next
For Each wp As WorkPlane In wpToDelete
    Try : wp.Delete() : Catch : End Try
Next

' === WINKEL VORAB BERECHNEN ===
Dim winkelListe As New List(Of Double)
Dim typListe As New List(Of Boolean) ' True = Hauptwurzel

For i As Integer = 0 To anzahlHaupt - 1
    Dim basis As Double = (2 * PI * i / anzahlHaupt)
    Dim offset As Double = (rng.NextDouble() - 0.5) * (2 * PI / anzahlHaupt) * winkelVariation
    winkelListe.Add(basis + offset)
    typListe.Add(True)
Next

For i As Integer = 0 To anzahlNeben - 1
    Dim basis As Double = (2 * PI * i / anzahlNeben) + (PI / anzahlHaupt)
    Dim offset As Double = (rng.NextDouble() - 0.5) * (2 * PI / anzahlNeben) * winkelVariation
    winkelListe.Add(basis + offset)
    typListe.Add(False)
Next

' === WURZELN ERZEUGEN ===
Dim wurzelnErzeugt As Integer = 0
Dim sweepsErzeugt As Integer = 0
Dim sweepFehler As New List(Of String)

For i As Integer = 0 To anzahlGesamt - 1
    Dim istHaupt As Boolean = typListe(i)
    Dim theta As Double = winkelListe(i)

    ' Klassen-spezifische Parameter
    Dim bLaenge As Double = If(istHaupt, hauptLaenge, nebenLaenge)
    Dim bAbsenk As Double = If(istHaupt, hauptAbsenkung, nebenAbsenkung)
    Dim bAnstieg As Double = If(istHaupt, hauptAnstieg, nebenAnstieg)
    Dim bBreite As Double = If(istHaupt, hauptBreite, nebenBreite)
    Dim bHoehe As Double = If(istHaupt, hauptHoehe, nebenHoehe)
    Dim bBreiteS As Double = If(istHaupt, hauptBreiteSpitze, nebenBreiteSpitze)
    Dim bHoeheS As Double = If(istHaupt, hauptHoeheSpitze, nebenHoeheSpitze)

    ' Individuelle Variation
    Dim indivLaenge As Double = bLaenge * (1.0 - laengenVariation * 0.5 + rng.NextDouble() * laengenVariation)
    Dim indivAbsenk As Double = bAbsenk * (0.6 + rng.NextDouble() * 0.8)
    Dim indivAnstieg As Double = bAnstieg * (0.7 + rng.NextDouble() * 0.6)
    Dim indivBreite As Double = bBreite * (0.85 + rng.NextDouble() * 0.3)
    Dim indivHoehe As Double = bHoehe * (0.85 + rng.NextDouble() * 0.3)

    ' VARIABLE L-KURVE: Phasengrenzen pro Wurzel unterschiedlich
    ' dropEnd: wann die Wurzel Bodenniveau erreicht (0.08-0.20)
    ' diveStart: wann sie in den Boden abtaucht (0.70-0.92)
    Dim dropEnd As Double = 0.08 + rng.NextDouble() * 0.12
    Dim diveStart As Double = 0.70 + rng.NextDouble() * 0.22
    ' Radialer Exponent: variabler Verlauf
    Dim radialExp As Double = 0.5 + rng.NextDouble() * 0.4

    Dim prefix As String = If(istHaupt, "Root_Main_", "Root_Side_")

    ' 3D-Skizze für Wurzel-Pfad
    Dim oSketch3D As Sketch3D = oDef.Sketches3D.Add()
    oSketch3D.Name = prefix & "Path_" & Format(i, "00")
    oSketch3D.Edit()

    Dim punkte As ObjectCollection = ThisApplication.TransientObjects.CreateObjectCollection()
    Dim pfadLaenge As Double = 0.0
    Dim prevX As Double = 0, prevY As Double = 0, prevZ As Double = 0

    For j As Integer = 0 To punkteProWurzel - 1
        Dim t As Double = j / CDbl(punkteProWurzel - 1) ' 0 bis 1

        ' Radialer Abstand
        Dim r As Double = stammRadius + indivLaenge * Math.Pow(t, radialExp)

        ' === L-FÖRMIGE Z-KURVE (stückweise) ===
        ' Phase 1: Schnell vom Stamm auf Bodenniveau fallen
        ' Phase 2: Lang flach am Boden entlang (leichte Wellung)
        ' Phase 3: Sanft in den Boden eintauchen
        Dim z As Double
        If t < dropEnd Then
            ' Phase 1: Quadratisch abfallend → schnell auf Z=0
            Dim tN As Double = t / dropEnd
            z = indivAnstieg * (1.0 - tN * tN)
        ElseIf t < diveStart Then
            ' Phase 2: Flach am Boden, minimale Wellung
            Dim tN As Double = (t - dropEnd) / (diveStart - dropEnd)
            Dim bodenWelle As Double = Math.Sin(tN * PI) * 0.12
            z = bodenWelle + (rng.NextDouble() - 0.5) * 0.05
        Else
            ' Phase 3: Quadratisch in den Boden
            Dim tN As Double = (t - diveStart) / (1.0 - diveStart)
            z = -indivAbsenk * tN * tN
        End If

        ' Laterale Welligkeit: minimal
        Dim welle As Double = Math.Sin(t * PI * (0.7 + rng.NextDouble() * 0.3)) * welligkeit
        welle += (rng.NextDouble() - 0.5) * welligkeit * 0.1
        Dim winkelAbw As Double = welle / r
        Dim aktWinkel As Double = theta + winkelAbw

        Dim x As Double = r * Math.Cos(aktWinkel)
        Dim y As Double = r * Math.Sin(aktWinkel)

        If j > 0 Then
            pfadLaenge += Math.Sqrt((x - prevX) ^ 2 + (y - prevY) ^ 2 + (z - prevZ) ^ 2)
        End If
        prevX = x : prevY = y : prevZ = z
        punkte.Add(oTG.CreatePoint(x, y, z))
    Next j

    ' Spline erzeugen
    Dim oSpline As SketchSpline3D = Nothing
    If punkte.Count >= 3 Then
        Try
            oSpline = oSketch3D.SketchSplines3D.Add(punkte)
            wurzelnErzeugt += 1
        Catch ex As Exception
            oSketch3D.ExitEdit()
            Continue For
        End Try
    End If
    oSketch3D.ExitEdit()
    If oSpline Is Nothing Then Continue For

    ' === SWEEP: Elliptisches Profil + Pfad + Taper ===
    Try
        ' WorkPlane senkrecht zum Spline am Startpunkt
        Dim oWP As WorkPlane = oDef.WorkPlanes.AddByNormalToCurve( _
            oSpline, oSpline.StartSketchPoint)
        oWP.Name = prefix & "WP_" & Format(i, "00")
        oWP.Visible = False

        ' Profil-Skizze: ELLIPSE (breit tangential, flach vertikal)
        Dim oSketch2D As PlanarSketch = oDef.Sketches.Add(oWP)
        oSketch2D.Name = prefix & "Profile_" & Format(i, "00")
        oSketch2D.Edit()
        Dim projPt As SketchPoint = oSketch2D.AddByProjectingEntity(oSpline.StartSketchPoint)
        ' Ellipse: MajorAxis in X-Richtung der Sketch-Ebene (≈ tangential zum Zylinder)
        ' MinorAxis in Y-Richtung (≈ vertikal/radial → flach)
        Dim centerPt As Point2d = oTG.CreatePoint2d(projPt.Geometry.X, projPt.Geometry.Y)
        Dim majorAxis As UnitVector2d = oTG.CreateUnitVector2d(1.0, 0.0) ' X-Richtung
        Dim majorRadius As Double = indivBreite / 2.0
        Dim minorRadius As Double = indivHoehe / 2.0
        oSketch2D.SketchEllipses.Add(centerPt, majorAxis, majorRadius, minorRadius)
        oSketch2D.ExitEdit()

        ' Profil und Pfad
        Dim oProfile As Profile = oSketch2D.Profiles.AddForSolid()
        Dim oPath As Path = oDef.Features.CreatePath(oSpline)

        ' Taper-Winkel: basierend auf durchschnittlicher Radiusänderung
        Dim avgRadiusStart As Double = (indivBreite + indivHoehe) / 4.0
        Dim avgRadiusEnd As Double = (bBreiteS + bHoeheS) / 4.0
        Dim taperWinkel As Double = 0.0
        If pfadLaenge > 0.1 Then
            taperWinkel = Math.Atan((avgRadiusStart - avgRadiusEnd) / pfadLaenge)
        End If

        ' Sweep mit Taper versuchen
        Try
            Dim oSweepDef As SweepDefinition = oDef.Features.SweepFeatures.CreateSweepDefinition( _
                SweepTypeEnum.kPathSweepType, _
                oProfile, oPath, _
                PartFeatureOperationEnum.kJoinOperation)
            oSweepDef.TaperAngle = -taperWinkel
            Dim oSweep As SweepFeature = oDef.Features.SweepFeatures.Add(oSweepDef)
            oSweep.Name = prefix & "Sweep_" & Format(i, "00")
            sweepsErzeugt += 1
        Catch
            ' Fallback: Sweep ohne Taper (gleiche API, nur TaperAngle weglassen)
            Try
                Dim oSweepDef2 As SweepDefinition = oDef.Features.SweepFeatures.CreateSweepDefinition( _
                    SweepTypeEnum.kPathSweepType, _
                    oProfile, oPath, _
                    PartFeatureOperationEnum.kJoinOperation)
                Dim oSweep2 As SweepFeature = oDef.Features.SweepFeatures.Add(oSweepDef2)
                oSweep2.Name = prefix & "Sweep_" & Format(i, "00")
                sweepsErzeugt += 1
                sweepFehler.Add(prefix & i & ": Taper fehlgeschlagen, konstantes Profil")
            Catch ex2 As Exception
                sweepFehler.Add(prefix & i & ": Sweep fehlgeschlagen – " & ex2.Message)
            End Try
        End Try

    Catch ex As Exception
        sweepFehler.Add(prefix & i & ": Profil/Sweep übersprungen – " & ex.Message)
    End Try

Next i

' === ERGEBNIS ===
oDoc.Update()

Dim fehlerText As String = ""
If sweepFehler.Count > 0 Then
    fehlerText = vbCrLf & vbCrLf & "Warnungen:" & vbCrLf
    For Each msg As String In sweepFehler
        fehlerText &= "  • " & msg & vbCrLf
    Next
End If

MessageBox.Show( _
    "Wurzel-Generator v3 abgeschlossen!" & vbCrLf & _
    "Haupt: " & anzahlHaupt & " + Neben: " & anzahlNeben & " = " & anzahlGesamt & vbCrLf & _
    "Spline-Pfade: " & wurzelnErzeugt & vbCrLf & _
    "Sweeps (Join): " & sweepsErzeugt & vbCrLf & _
    "Profil: Ellipse (breit/flach)" & vbCrLf & _
    "Z-Kurve: L-förmig (Drop→Flat→Dive)" & vbCrLf & _
    "Haupt: " & hauptBreite & "×" & hauptHoehe & "cm, " & hauptLaenge & "cm lang" & vbCrLf & _
    "Neben: " & nebenBreite & "×" & nebenHoehe & "cm, " & nebenLaenge & "cm lang" & _
    fehlerText & vbCrLf & vbCrLf & _
    "Fillets: manuell setzen für organischen Übergang" & vbCrLf & _
    "Seed: " & seed & " (ändern für anderes Muster)", _
    "Elder-Berry Root Generator v3")
